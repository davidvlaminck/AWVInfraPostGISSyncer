FME workspace import_gemeenten.fmw
Title: Import gemeenten Vlaanderen en Brussel naar PostGIS
History: 25.03.2025,Dries Verdoodt | dries.verdoodt@mow.vlaanderen.be,initial workspace to retreive data and write to the database

Parameters:
- DestDataset_POSTGIS = localhost_infradb   # Connection

Writers:
- POSTGIS_1: POSTGIS to $(DestDataset_POSTGIS) in EPSG:31370

Creator
    GEOMTYPE = Geometry Object
    NUM = 1
    CREATED -> FeatureReader [INITIATOR]
    CREATED -> FeatureReader_2 [INITIATOR]
Note: Gemeenten in Vlaanderen
FeatureReader_2
    ATTRIBUTES = Refgem,"gml_parent_id,gml_parent_property,gml_id,UIDN,OIDN,TERRID,TERRID.xsi_nil,NISCODE,NISCODE.xsi_nil,NAAM,NAAM.xsi_nil,DATPUBLBS,DATPUBLBS.xsi_nil,NUMAC,NUMAC.xsi_nil,SHAPE,wfs_title",Refprv,"gml_parent_id,gml_parent_property,gml_id,UIDN,OIDN,TERRID,TERRID.xsi_nil,NAAM,NAAM.xsi_nil,NISCODE,NISCODE.xsi_nil,NUTS2,NUTS2.xsi_nil,SHAPE,wfs_title"
    ATTR_ACCUM_MODE = Only Use Result
    CLIP_TO_ENVELOPE = NO
    COMBINE_GEOM = Use Result
    COORDSYS = EPSG:31370
    DATASET = https://geo.api.vlaanderen.be/VRBG/wfs
    FEATURETYPES = Refgem Refprv
    FORMAT = WFS
    GEOMETRY_TYPES = Refgem,""",fme_area""",Refprv,""",fme_area"""
    INTERACT = NONE
    ORDER_RESULTS = No
    OUTPUT_ADD_SCHEMA_ATTRIBUTES = NO
    OUTPUT_FEATURES_DISPLAY = Schema and Data Features
    WFS_CONNECTION_TIMEOUT = 90
    WFS_DISABLE_AUTOMATIC_READER_TYPE_SELECTION = NO
    WFS_DISABLE_XML_NAMESPACE_PROCESSING = NO
    WFS_ENFORCE_PATH_CONTINUITY_BY = SNAPPING_END_POINTS
    WFS_FLATTEN_XML_FRAGMENTS = NO
    WFS_GETFEATURE_PROCESSING_MODE = STREAM_MODE
    WFS_IGNORE_APPLICATON_SCHEMA = no
    WFS_IGNORE_GETFEATURE_ERROR = No
    WFS_LOCAL_CACHE_EXPIRY = 60
    WFS_MAP_COMPLEX_PROPERTIES_AS = Nested Attributes
    WFS_MAP_COVERAGES_AS_FEATURE_TYPES = NO
    WFS_MAP_EMBEDDED_OBJECTS_AS = ATTRIBUTES
    WFS_MAP_GEOMETRY_COLUMNS = YES
    WFS_MAP_PREDEFINED_GML_PROPERTIES = NO
    WFS_MAX_RESULT_FEATURES = 30000
    WFS_OMIT_BBOX_CRSURI_IN_URL = No
    WFS_OMIT_NAMESPACES_KEYWORD_IN_URLS = No
    WFS_PREFERRED_VERSION = 2.0.0
    WFS_PREFER_DATASET_URL = No
    WFS_PREFER_POST = No
    WFS_PREFIX_FEATURE_TYPES_ON_NAME_CLASH = YES
    WFS_SEPARATE_TYPENAMES_WITH_COMMAS = No
    WFS_TRANSFER_TIMEOUT = 90
    WFS_USE_OLD_READER = NO
    WFS_USE_SEARCH_ENVELOPE = NO
    WFS_WFS_EXPOSE_FORMAT_ATTRS = wfs_title,xml_buffer
    WFS_XML_FRAGMENTS_AS_DOCUMENTS = YES
    Refgem -> AttributeManager_2
AttributeManager_2
    ATTR_TABLE:
      RENAME_SET_VALUE NISCODE > niscode (buffer)
      RENAME_SET_VALUE NAAM > gemeente (buffer)
      SET_TO _niscode_eerste_letter (varchar(200)) = @Left(@Value(niscode),1)
      REMOVE gml_parent_id (buffer)
      REMOVE gml_parent_property (buffer)
      REMOVE gml_id (buffer)
      REMOVE UIDN (real64)
      REMOVE OIDN (real64)
      REMOVE TERRID (real64)
      REMOVE TERRID.xsi_nil (logical)
      REMOVE NISCODE.xsi_nil (logical)
      REMOVE NAAM.xsi_nil (logical)
      REMOVE DATPUBLBS (buffer)
      REMOVE DATPUBLBS.xsi_nil (logical)
      REMOVE NUMAC (buffer)
      REMOVE NUMAC.xsi_nil (logical)
      REMOVE SHAPE (buffer)
      REMOVE wfs_title (buffer)
    -> AttributeValueMapper
Note: Map de provincienaam op basis van de eerste letter van de niscode.
AttributeValueMapper
    DEFAULT_VALUE = FME_NULL_VALUE
    LUT = 1,Antwerpen,2,Vlaams-Brabant,3,West-Vlaanderen,4,Oost-Vlaanderen,7,Limburg
    MAPPING_DIRECTION = FORWARD
    SRC = _niscode_eerste_letter
    VAL_ATTR = provincie
    -> Junction
Note: Gemeenten in het BHG
FeatureReader
    ATTRIBUTES = Municipalities,"gml_parent_id,gml_parent_property,gml_id,NISCODE,NISCODE.xsi_nil,NAMEFRE,NAMEFRE.xsi_nil,NAMEDUT,NAMEDUT.xsi_nil,POLICEZONE,POLICEZONE.xsi_nil,AREA,AREA.xsi_nil,INSPIRE_ID,INSPIRE_ID.xsi_nil,GEOM"
    ATTR_ACCUM_MODE = Only Use Result
    CLIP_TO_ENVELOPE = NO
    COMBINE_GEOM = Use Result
    COORDSYS = EPSG:31370
    DATASET = https://geoservices-urbis.irisnet.be/geoserver/urbisvector/wfs?request=GetCapabilities&service=WFS&version=2.0.0
    FEATURETYPES = Municipalities
    FORMAT = WFS
    GEOMETRY_TYPES = Municipalities,""",fme_area,fme_collection,fme_line,fme_point,fme_solid,fme_surface"""
    INTERACT = NONE
    ORDER_RESULTS = No
    OUTPUT_ADD_SCHEMA_ATTRIBUTES = NO
    OUTPUT_FEATURES_DISPLAY = Schema and Data Features
    WFS_CONNECTION_TIMEOUT = 90
    WFS_DISABLE_AUTOMATIC_READER_TYPE_SELECTION = NO
    WFS_DISABLE_XML_NAMESPACE_PROCESSING = NO
    WFS_ENFORCE_PATH_CONTINUITY_BY = SNAPPING_END_POINTS
    WFS_FLATTEN_XML_FRAGMENTS = NO
    WFS_GETFEATURE_PROCESSING_MODE = STREAM_MODE
    WFS_IGNORE_APPLICATON_SCHEMA = no
    WFS_IGNORE_GETFEATURE_ERROR = No
    WFS_LOCAL_CACHE_EXPIRY = 60
    WFS_MAP_COMPLEX_PROPERTIES_AS = Nested Attributes
    WFS_MAP_COVERAGES_AS_FEATURE_TYPES = NO
    WFS_MAP_EMBEDDED_OBJECTS_AS = ATTRIBUTES
    WFS_MAP_GEOMETRY_COLUMNS = YES
    WFS_MAP_PREDEFINED_GML_PROPERTIES = NO
    WFS_MAX_RESULT_FEATURES = 30000
    WFS_OMIT_BBOX_CRSURI_IN_URL = No
    WFS_OMIT_NAMESPACES_KEYWORD_IN_URLS = No
    WFS_PREFERRED_VERSION = 1.1.0
    WFS_PREFER_DATASET_URL = No
    WFS_PREFER_POST = No
    WFS_PREFIX_FEATURE_TYPES_ON_NAME_CLASH = YES
    WFS_TRANSFER_TIMEOUT = 90
    WFS_USE_OLD_READER = NO
    WFS_USE_SEARCH_ENVELOPE = NO
    WFS_XML_FRAGMENTS_AS_DOCUMENTS = YES
    Municipalities -> AttributeManager
AttributeManager
    ATTR_TABLE:
      SET_TO niscode (varchar(200)) = @Value(NISCODE)
      SET_TO gemeente (varchar(200)) = @Value(NAMEDUT)
      SET_TO provincie (varchar(30)) = Brussels Hoofdstedelijk Gewest
    -> Junction
Junction
    -> VertexCounter
Note: Truncate existing table
gemeente (writer POSTGIS_1)
    attributes: gemeente varchar(64),Unique, niscode varchar(5),Unique, provincie varchar,BTree

Bookmark: Generalize geometry
VertexCounter
    CNT_ATTR = _vertexcount_before
    -> Generalizer
Note: Maximum 25 meter to prevent creating incorrect geometries
Generalizer
    ALG = Douglas
    CLEANING_TOLERANCE_LOOKUP = AUTO
    PRESERVE = Yes
    PRESERVE_PATHS_LOOKUP = YES
    TOLERANCE = 25
    ALG_TEXT = Douglas (Generalize)
    CLEANING_TOLERANCE = Automatic
    PRESERVE_PATHS = Yes
    -> VertexCounter_2
VertexCounter_2
    CNT_ATTR = _vertexcount_after
    -> GeometryValidator_2
GeometryValidator_2
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> gemeente (writer POSTGIS_1)
    FAILED -> Terminator
Terminator
    MESSAGE = Translation Terminated
